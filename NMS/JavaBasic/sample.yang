module network-config {
    namespace "urn:example:network-config";
    prefix "nc";

    organization "Example Corp";
    contact "support@example.com";
    description "A simple YANG model for network configuration.";

    revision "2025-03-08" {
        description "Initial revision.";
    }

    container network {
        description "Network configuration container.";

        leaf hostname {
            type string;
            description "Device hostname.";
        }

        leaf ip-address {
            type string;
            description "IPv4 address of the device.";
        }

        leaf subnet-mask {
            type string;
            description "Subnet mask of the network.";
        }

        leaf enable-ssh {
            type boolean;
            default "true";
            description "Enable SSH access.";
        }
    }
}
